FME workspace fme_mapeamento.fmw

Parameters:
- direcao = volta   # Direção do mapeamento
- JsonMapeamento = $(FME_MF_DIR)conversao_dsgtools_gothic_213.json   # Arquivo de mapeamento
- DestDataset_POSTGIS = asc_50k_gothic_sad_21s   # Database
- COORDSYS = SAD69.UTM-21S   # Coordinate System
- SourceDataset_POSTGIS = asc_50k_gothic_sad_21s   # Database
- SourceDataset_FFS = \\10.25.163.4\Tabelas_FME\Generalizacao\Dados_Originais\NOVO\E2_SG_21_Z_D_S69_57S_V2.1_GEN.ffs   # Source FME Feature Store (FFS) File(s)
- FEATURE_TYPES =

Readers:
- POSTGIS_1: POSTGIS from $(SourceDataset_POSTGIS)
- FFS_1: FFS from $(SourceDataset_FFS)

Writers:
- POSTGIS_2: POSTGIS to $(DestDataset_POSTGIS)

Aglomerado_Rural (reader FFS_1)
    attributes: tipoAglomerado int32, geometriaAproximada int32, offSetSimbX real32, identificadorPosicGeo char(255), orientacao real32, geocodigo char(255), nome char(255), simbolizar logical, longitude real32, offSetY real32, justTxt int32, offSetX real32, offSetSimbY real32, latitude real32, latitude_gms char(255), nomeAbrev char(255), longitude_txt char(255), longitude_gms char(255), simbolizarCartaMini logical, tamanhoTxt real32, latitude_txt char(255), fkClassificador char(255), jurisdicao int32, salinidade int32, alturaEstimada real32, causaExposicao int32, sistemaGeodesico int32, fkComplMilitar char(255), fkComplOrgAgrop char(255), ordemTickDepressao int32,
      markup_ticked logical, fkComplRodovia char(255), repTipoTxt int32, relacionado int32, concessionaria char(255), situacaoCosta int32, atividade int32, tipoExtMin int32, fkComplDuto char(255), procExtracao int32, nomeTi char(255), tipoSinal int32, tipoCemiterio int32, situacaoEmAgua int32, fkComplEstrApoio char(255), tipoProdutoResiduo int32, situacaoJuridica int32, nrLinhas int32, gabHorizSup real32, tipoLimPol int32, numPartes char(255), situacaoAgua int32, offSetXTipo real32, bitola int32, tensaoEletrica real32, gabVertSup real32, motivoDescontinuidade int32, tipoQueda int32, tipoUsoEdif int32, tipoRecife int32,
      tipoLimMassa int32, markup_show_note logical, grupoEtnico char(255), numCircuitos int32, tipoMarcoLim int32, usoPrincipal int32, trafego int32, codTrechoRodov char(255), justTxtAltitude int32, referencialAltim int32, espacamentoPalavra real32, fkComplCom char(255), fkComplTrCurDagua char(255), posicaoPista int32, filter real32, atoLegal char(255), posicaoRelEdific int32, nrDutos int32, areaOficialHa real32, necessidadeManutencao int32, tipoDelimFis int32, setor int32, situacaoEspacial int32, tipoTrechoDuto int32, tipoTerrExp int32, formaExtracao int32, administracao int32, dataSituacaoJuridica char(255), fkComplPortuario char(255), chamine int32,
      offSetYAltitude real32, tipoClasseCnae int32, tipoEntroncamento int32, tipoSumVert int32, fkComplOrgEnsino char(255), sigla char(255), dataVisita char(255), tipoEdifComercServ int32, potenciaFiscalizadaKW real32, markup_visited_permanently logical, tipoSecaoCnae int32, vaoLivreHoriz real32, referencialGrav int32, fkComplAbsAgua char(255), offSet real32, tipoMassaDagua int32, tipoTravessiaPed int32, tipoDepGeral int32, offSetYTipo real32, fkComplOrgExtMin char(255), dentroDePoligono int32, tipoAreaUsoComun int32, tipoPista int32, outraRefAlt char(255), obs char(255), tipoUnidProtInteg int32, tratamento int32, posicaoRelativa int32, tipoPassagViad int32, visivel int32,
      periodicidadeInunda char(255), eixoPrincipal int32, codTrechoFerrov int32, tipoEdifAero int32, nrPistas int32, ovgd int32, fkComplGerEnEletr char(255), larguraMedia real32, largura real32, orgaoEnteResp char(255), fkComplComunic char(255), profundidadeMedia real32, nrFaixas int32, outraRefPlan char(255), emMassaDagua int32, tipoCidade int32, modalUso int32, emArruamento int32, matConstr int32, espacamentoLetra real32, pesoMaxSuportTon real32, fkComplAeroport char(255), areaOficial char(255), perimetroOficial real32, homologacao int32, tipoDivisaoCnae int32, situacaoMarco int32, fkComplOrgRel char(255), tipoLimAreaEsp int32, tipoExposicao int32,
      ensino int32, velocidadeMedia int32, tipoTorre int32, fixa int32, finalidade int32, tipoTrechoRod int32, cotaComprovada int32, justTxtTipo int32, proximidade int32, fkComplSubEnEletr char(255), situacaoFisica int32, smooth real32, arranjoFases char(255), tipoPtoEnergia int32, extensao real32, fkComplPubCivil char(255), unidadeVolume int32, tipoEdifPort int32, tipoPonte int32, potenciaFiscalizada int32, altitudeOrtometrica real32, tipoTrechoFerrov int32, especie int32, destEnergElet int32, revestimento int32, altura real32, denominacaoAssociada int32, valorVolume real32, fkComplLazer char(255), tipoTrechoComunic int32,
      depressao int32, tipoAlterAntrop int32, tipoRepresentacao int32, compartilhado int32, navegabilidade int32, motivo int32, causa int32, funcaoEdifMetroFerrov int32, destinacaoFundeadouro int32, fkComplIndustria char(255), caladoMax real32, escalaDosDadosEDGV real32, alturaLamina real32, tipoRef int32, tipoConteudo int32, velocidadeMedCorrente real32, tipoTunel int32, nivelAtencao int32, emDuto int32, eletrificada int32, potenciaOutorgadaKW real32, escalaMaxSimbolizar int32, coincideComDentroDe int32, tipoEdifAgropec int32, tipoEstGerad int32, codPonto char(255), tipoElemNat int32, situaMare int32, fkComplSaude char(255), matTransp int32,
      usoPista int32, fkComplOrgComSv char(255), canteiroDivisorio int32, markup_note_text char(255), tipoEdifRelig int32, operacional int32, anoCriacao int32, tipoPtoRefGeodTopo int32, obsSituacao char(255), indice int32, potenciaOutorgada int32, tipoEdifLazer int32, materialPredominante int32, religiao char(255), offSetXAltitude real32, fkComplHidrovia char(255), tipoDepAbast int32, fkComplHabit char(255), nascente int32, alturaMediaMargem real32, tipoEdifEnergia int32, fkComplFerrovia char(255), regime int32, rede int32, orgResp char(255), codigoEstacao char(255), tipoPocoMina int32, vaoVertical real32, tipoEdif int32, cota int32,
      cotadaPorProcesso int32, construcao int32, tipoTravessia int32, multimodal int32, tipoAreaUmida int32
    -> Junction
Junction
    -> Tester_12
Tester_12
    BOOL_OP = OR
    TEST_CLAUSE = TEST tipoSecaoCnae ATTRIBUTE_IS_MISSING ""
    PASSED -> Tester_11
    FAILED -> tiposecaocnae
tiposecaocnae: AttributeCreator
    ATTR_TABLE = SET_TO tipoSecaoCnae
    -> Tester_11
Tester_11
    BOOL_OP = OR
    TEST_CLAUSE = TEST coincideComDentroDe ATTRIBUTE_IS_MISSING ""
    PASSED -> coincidecomdentrode
    FAILED -> Tester_10
coincidecomdentrode: AttributeCreator
    ATTR_TABLE = SET_TO coincideComDentroDe
    -> Tester_10
Tester_10
    BOOL_OP = OR
    TEST_CLAUSE = TEST tipoTunel ATTRIBUTE_IS_MISSING ""
    PASSED -> tipotunel
    FAILED -> Tester_9
tipotunel: AttributeCreator
    ATTR_TABLE = SET_TO tipoTunel
    -> Tester_9
Tester_9
    BOOL_OP = OR
    TEST_CLAUSE = TEST situacaoFisica ATTRIBUTE_IS_MISSING ""
    PASSED -> situaMare_3
    FAILED -> Tester_8
situaMare_3: AttributeCreator
    ATTR_TABLE = SET_TO situacaoFisica
    -> Tester_8
Tester_8
    BOOL_OP = OR
    TEST_CLAUSE = TEST operacional ATTRIBUTE_IS_MISSING ""
    PASSED -> situaMare_2
    FAILED -> Tester_7
situaMare_2: AttributeCreator
    ATTR_TABLE = SET_TO operacional
    -> Tester_7
Tester_7
    BOOL_OP = OR
    TEST_CLAUSE = TEST situaMare ATTRIBUTE_IS_MISSING ""
    PASSED -> situaMare
    FAILED -> Tester_6
situaMare: AttributeCreator
    ATTR_TABLE = SET_TO situaMare
    -> Tester_6
Tester_6
    BOOL_OP = OR
    TEST_CLAUSE = TEST canteiroDivisorio ATTRIBUTE_IS_MISSING ""
    PASSED -> canteirodivisorio
    FAILED -> Tester_5
canteirodivisorio: AttributeCreator
    ATTR_TABLE = SET_TO canteiroDivisorio
    -> Tester_5
Tester_5
    BOOL_OP = OR
    TEST_CLAUSE = TEST motivoDescontinuidade ATTRIBUTE_IS_MISSING ""
    PASSED -> motivodescontinuidade
    FAILED -> Tester_3
motivodescontinuidade: AttributeCreator
    ATTR_TABLE = SET_TO motivoDescontinuidade
    -> Tester_3
Tester_3
    BOOL_OP = OR
    TEST_CLAUSE = TEST tipoAreaUmida ATTRIBUTE_IS_MISSING ""
    PASSED -> tipoAreaUmida
    FAILED -> Tester_2
tipoAreaUmida: AttributeCreator
    ATTR_TABLE = SET_TO tipoAreaUmida
    -> Tester_2
Tester_2
    BOOL_OP = OR
    TEST_CLAUSE = TEST situacaoEspacial ATTRIBUTE_IS_MISSING ""
    PASSED -> destEnergElet_2
    FAILED -> Tester
destEnergElet_2: AttributeCreator
    ATTR_TABLE = SET_TO situacaoEspacial
    -> Tester
Tester
    BOOL_OP = OR
    TEST_CLAUSE = TEST destEnergElet ATTRIBUTE_IS_MISSING ""
    PASSED -> destEnergElet
    FAILED -> NullAttributeMapper
destEnergElet: AttributeCreator
    ATTR_TABLE = SET_TO destEnergElet
    -> NullAttributeMapper
Note: FFS transformou alguns atributos nulos em missing, o que afeta o mapeamento
NullAttributeMapper
    ATTRCHOICE = Selected Attributes
    ATTRLIST = tipoSinal tipoLavoura formaExtracao tipoEdif latitude_txt alturaMediaMargem tipoCampoQuadra naMaximoOperacional emArruamento latitude cotaComprovada tipoEntroncamento sigla justTxtAltitude velocidadeMedia materialPredominante modalUso usoPrincipal nome tipoSecaoCnae markup_note_text situacaoMarco tipoEdifAgropec tipoMacChav altitudeOrtometrica fkComplDuto tipoUsoEdif sistemaGeodesico tratamento tipoCampo tipoTorre comprimentoTraco extensao fkComplSubEnEletr codPonto fkComplEstrApoio tipoEdifEnergia tamanhoTxt visivel tipoAtracad tipoEdifAero anoCriacao procExtracao outraRefAlt tipoEdifComunic denso fkClassificador funcaoEdifMetroFerrov tipoEdifPort codEstacao tipoCidade tipoQueda tipoTrechoDuto compartilhado tipoFonteDagua modalidade ovgd multimodal tipoPocoMina gabVertSup proximidade escalaMaxSimbolizar matTransp residuo codTrechoRodov areaOficialHa tipoSumVert destEnergElet relacionado tipoPonte identificadorPosicGeo longitude_txt situacaoJuridica tipoPtoEnergia tipoOutUnidProt indice salinidade referencialGrav necessidadeManutencao dentroDePoligono _codigo_aquisicao nrFaixas offSetY tipoTravessia terreno gabHorizSup nrPistas espacamentoLetra tipoDepSaneam tipoDelimFis dataSituacaoJuridica tipoEdifTurist fkComplFerrovia nrLinhas tipoElemNat filter offSetSimbX historicoModificacao espacamentoPalavra markup_ticked offSetXTipo qualidAgua coletiva fonteTxt tipoBanco situacaoAgua tipoRef tipoExposicao justTxtTipo situacaoEmAgua posicaoPista administracao fkComplAeroport emDuto tipoPassagViad nascente religiao situacaoFisica tipoLimPol motivoDescontinuidade fkComplHidrovia canteiroDivisorio tipoLimAreaEsp tipoEdifLazer tipoTerrExp homologacao tipoEdifAbast nomeAbrev velocidadeMedCorrente smooth tipoProdutoResiduo tipoObst potenciaOutorgadaKW setor caracteristicaFloresta numPartes materializado ordemTickDepressao fkComplOrgExtMin fkComplCom denominacaoAssociada fkComplOrgEnsino orgResp jurisdicao cor tipoTunel usoPista comprimentoBranco cotadaPorProcesso cultivoPredominante atoLegal tipoBrejoPantano codigoEstacao matConstr fkComplGerEnEletr naMaximoMaximorum situacaoEspacial bitola classificacao fkComplPortuario ocorrenciaEm orientacao tensaoEletrica tipoLimMassa geracao isolada eletrificada tipoClasseCnae fkComplOrgRel revestimento fkComplSaude fkComplSvSoc regime tipoQuebramarMolhe largura tipoUnidProtInteg causa combRenovavel fme_feature_type trafego offSetYAltitude tipoCaminhoAereo especie tipoAreaUsoComun concessionaria tipoLocalCrit fkComplEstMedFen tipoMassaDagua justTxt perimetroOficial referencialAltim tipoPtoControle altura areaOficial finalidade espessuraDAP fkComplComunic estilo atividade markup_visited_permanently nomeTi coincideComDentroDe profundidadeMedia markup_show_note tipoTravessiaPed eixoPrincipal antropizada emMassaDagua categoriaEDGV tipoDepGeral numCircuitos offSetSimbY depressao fkComplRodovia tipoRecife arranjoFases fixa situacaoCosta nrDutos fkComplHabit dataVisita longitude operacional motivo fkComplOrgAgrop codigoOtto desnivel geometriaAproximada periodicidadeInunda fkComplAbsAgua tipoTrechoFerrov volumeUtil posicaoRelativa simbolizar tipoAreaUmida vaoLivreHoriz larguraMedia tipoEdifRelig tipoCombustivel ensino nivelOtto construcao vaoVertical navegabilidade tipoTrechoComunic posicaoRelEdific tipoEdifSaneam situaMare potenciaFiscalizadaKW rede tipoUsoCaminhoAer tipoAglomerado tipoAlterAntrop escalaDosDadosEDGV fkComplTrCurDagua tipoPtoRefGeodTopo codTrechoFerrov tipoDepAbast fkComplLazer tipoDivisaoCnae pesoMaxSuportTon cota alturaEstimada causaExposicao fkComplIndustria codProjeto fkComplAldeia alturaMediaIndividuos tipoPtoEstMed fkComplSaneam unidadeVolume espessAlgas repTipoTxt offSetYTipo obsSituacao tipoCemiterio offSetX tipoPista calado corTxt obsAquisicao tipoExtMin offSetXAltitude tipoConteudo caladoMax tipoRepresentacao tipoTrechoRod valorVolume controleId especiePredominante fkComplOrgComSv alturaLamina fkComplMilitar chamine simbolizarCartaMini obs tipoEdifComercServ classificacaoPorte corContorno orgaoEnteResp nivelAtencao grupoEtnico tipoMarcoLim tipoMaqTermica espacamentoIndividuos offSet fkComplPubCivil tipoResiduo tipoEstGerad outraRefPlan tipoEdifRod
    NULL_TREATMENT = Null
    SOURCE_ATTR_VAL = "Missing (Selected Attributes Only)"
    -> AttributeEncoder
Note: atributos tem que ser UTF-8
AttributeEncoder
    ATTRCHOICE = All Attributes
    DEST_ENCODING = utf-8
    TREAT_AS_BYTES = Honor Encoding
    -> CoordinateSystemSetter
Note: ffs está sem sistema
CoordinateSystemSetter
    COORDSYS = $(COORDSYS)
    -> PythonCaller_2
Note: mapeamento
PythonCaller_2
    NEW_ATTRIBUTES = CLASS_NOT_FOUND
    PYTHONSOURCE:
      import fme
      import fmeobjects
      import copy
      import sys
      import os
      import json

      class FeatureProcessor(object):
          def __init__(self):
              self.mappingDict = self.buildFileDict(FME_MacroValues['JsonMapeamento'])
              self.mappingType = FME_MacroValues['direcao']

          def buildFileDict(self, mappingPath):
              file = open(mappingPath, 'r')
              data = file.read()
              mapDict = json.loads(data)
              return mapDict

          def buildFeatureDict(self, feature):
              featDict = dict()
              for attr in feature.getAllAttributeNames():
                  if attr == 'fme_feature_type' or ('multi_writer' not in attr and 'multi_reader_' not in attr and 'fme_' not in attr and 'postgis_' not in attr):
                      if feature.getAttribute(attr) or feature.getAttribute(attr) == 0:
                          featDict[attr] = feature.getAttribute(attr)
                      else:
                          featDict[attr] = None
              if feature.performFunction('@GeometryType()') == 'fme_polygon':
                  featDict["$GEOM_TYPE"] = 'POLYGON'
              elif feature.performFunction('@GeometryType()') == 'fme_line':
                  featDict["$GEOM_TYPE"] = 'LINESTRING'
              elif feature.performFunction('@GeometryType()') == 'fme_point':
                  featDict["$GEOM_TYPE"] = 'POINT'
              return featDict

          def evaluateExpression(self, featDict, expression):
              return expression["nome_atributo"] in featDict and featDict[expression["nome_atributo"]] == expression["valor"]

          def evaluateFilter(self, featDict, filter_condition):
              if "$and" in filter_condition:
                  return all([self.evaluateFilter(featDict, condition) for condition in filter_condition["$and"]])
              elif "$or" in filter_condition:
                  return any([self.evaluateFilter(featDict, condition) for condition in filter_condition["$or"]])
              elif "$not" in filter_condition:
                  return not self.evaluateFilter(featDict, filter_condition["$not"])
              else:
                  return self.evaluateExpression(featDict, filter_condition)

          def convertFeature(self, featDict):
              if self.mappingType == "ida":
                  key_attr_origin = "attr_ida"
                  key_attr_destiny = "attr_volta"
                  key_value_origin = "valor_ida"
                  key_value_destiny = "valor_volta"
                  default_key = "atributos_default_ida"
                  filter_key = "filtro_ida"
                  key_class_origin = "classe_ida"
                  key_class_destiny = "classe_volta"
                  key_group_origin = "tupla_ida"
                  key_group_destiny = "tupla_volta"
              else:
                  key_attr_origin = "attr_volta"
                  key_attr_destiny = "attr_ida"
                  key_value_origin = "valor_volta"
                  key_value_destiny = "valor_ida"
                  default_key = "atributos_default_volta"
                  filter_key = "filtro_volta"
                  key_class_origin = "classe_volta"
                  key_class_destiny = "classe_ida"
                  key_group_origin = "tupla_volta"
                  key_group_destiny = "tupla_ida"

              should_map = False
              for classmap in self.mappingDict['mapeamento_classes']:
                  if "sentido" not in classmap or ("sentido" in classmap and classmap["sentido"] == self.mappingType):
                      if classmap[key_class_origin] == featDict["fme_feature_type"]:
                          should_map = True
              if not should_map:
                  featDict["CLASS_NOT_FOUND"] = True
                  return featDict

              mappedFeat = copy.deepcopy(featDict)

              for attmap in self.mappingDict['mapeamento_atributos']:
                  if attmap[key_attr_origin] in featDict:
                      mappedFeat[attmap[key_attr_destiny]] = featDict[attmap[key_attr_origin]]
                      if "traducao" in attmap:
                          for valuemap in attmap["traducao"]:
                              if valuemap[key_value_origin] == featDict[attmap[key_attr_origin]] and ("sentido" not in valuemap or ("sentido" in valuemap and valuemap["sentido"] == self.mappingType)):
                                  mappedFeat[attmap[key_attr_destiny]] = valuemap[key_value_destiny]

              for classmap in self.mappingDict['mapeamento_classes']:
                  if "sentido" not in classmap or ("sentido" in classmap and classmap["sentido"] == self.mappingType):
                      if classmap[key_class_origin] == featDict["fme_feature_type"]:
                          if filter_key in classmap:
                              if not self.evaluateFilter(featDict, classmap[filter_key]):
                                  continue

                          mappedFeat["fme_feature_type"] = classmap[key_class_destiny]

                          if default_key in classmap:
                              for default in classmap[default_key]:
                                  mappedFeat[default["nome_atributo"]] = default["valor"]

                          if "traducao_atributos" in classmap:
                              for attmap in classmap['traducao_atributos']:
                                  if attmap[key_attr_origin] in featDict:
                                      if attmap[key_attr_destiny] not in mappedFeat:
                                          mappedFeat[attmap[key_attr_destiny]] = featDict[attmap[key_attr_origin]]
                                      if "traducao" in attmap:
                                          for valuemap in attmap["traducao"]:
                                              if valuemap[key_value_origin] == featDict[attmap[key_attr_origin]] and ("sentido" not in valuemap or ("sentido" in valuemap and valuemap["sentido"] == self.mappingType)):
                                                  mappedFeat[attmap[key_attr_destiny]] = valuemap[key_value_destiny]

                          if "mapeamento_atributos" in classmap:
                              for attmap in classmap['mapeamento_atributos']:
                                  if "sentido" not in attmap or ("sentido" in attmap and attmap["sentido"] == self.mappingType):
                                      if all([self.evaluateExpression(featDict, condition) for condition in attmap[key_group_origin]]):
                                          for valuemap in attmap[key_group_destiny]:
                                              mappedFeat[valuemap["nome_atributo"]] = valuemap["valor"]
                          break

              return mappedFeat

          def mapDictToFeature(self, feat, featDict):
              for attr, value in featDict.iteritems():
                  if value or value == 0:
                      feat.setAttribute(attr, u'{0}'.format(value))
                  else:
                      feat.setAttribute(attr, None)
              return feat

          def input(self,feature):
              feat = self.buildFeatureDict(feature)
              outputFeatDict = self.convertFeature(feat)
              if "CLASS_NOT_FOUND" in outputFeatDict and not outputFeatDict["CLASS_NOT_FOUND"]:
                  feature.setAttribute("CLASS_NOT_FOUND", u'True')
                  self.pyoutput(feature)
              else:
                  outputFeature = self.mapDictToFeature(feature, outputFeatDict)
                  self.pyoutput(outputFeature)

          def close(self):
              pass
    PYTHONSYMBOL = FeatureProcessor
    -> Tester_4
Tester_4
    BOOL_OP = OR
    TEST_CLAUSE = TEST @Value(CLASS_NOT_FOUND) = True
    PASSED -> Tester_4_Passed
    FAILED -> Counter
Tester_4_Passed: Inspector
Table1 (writer POSTGIS_2)

Bookmark: DSGTools as geometrias são multi
Counter
    CNT_ATTR = _count
    DOMAIN = counter
    SCOPE = Global
    START = 0
    -> Aggregator
Aggregator
    ACCUM_ATTRS_NAME = Use Attributes From One Feature
    AGGREGATE_TYPE = Homogeneous Collection (If Possible)
    GROUP_BY = _count
    MODE = Geometry - Assemble One Level
    ORDERED = Yes
    SEP = ,
    AGGREGATE -> GeometryFilter

Bookmark: Quebra as classes por tipo de geometria e ajusta o fme_feature_type de acordo
GeometryFilter
    BREAK_AGG = No
    GEOM_PORT_NAMES = Point Line Area
    POINT -> AttributeCreator
    LINE -> AttributeCreator_2
    AREA -> AttributeCreator_3
AttributeCreator
    ATTR_TABLE = SET_TO fme_feature_type = @Value(fme_feature_type)_p
    -> Table1 (writer POSTGIS_2)
AttributeCreator_2
    ATTR_TABLE = SET_TO fme_feature_type = @Value(fme_feature_type)_l
    -> Table1 (writer POSTGIS_2)
AttributeCreator_3
    ATTR_TABLE = SET_TO fme_feature_type = @Value(fme_feature_type)_a
    -> Table1 (writer POSTGIS_2)
