FME workspace atributos_dsgtools.fmw

Parameters:
- DestDataset_CSV2 = E:\DINIZ\3_Desenvolvimento\edgv_2.1.3_pro\conversao_gothic   # Destination CSV (Comma Separated Value) Folder

Writers:
- CSV2_1: CSV2 to $(DestDataset_CSV2)

SQLCreator
    DATASET = modelo_dsgtools
    EXPOSED_ATTRIBUTE_LIST = table_name,column_name,data_type
    FORMAT = POSTGIS
    POSTGIS_DISABLE_COLLECTION_SPLITTING = yes
    POSTGIS_HOST = 10.25.163.12
    POSTGIS_PASSWORD =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
    POSTGIS_PORT = 5432
    POSTGIS_QUERY_FEATURE_TYPES_FOR_MERGE_FILTERS = Yes
    POSTGIS_READ_TIME_WITH_TIMEZONE = Yes
    POSTGIS_SCHEMAS_FOR_TABLE_LISTING = cb
    POSTGIS_USER_NAME = postgres
    POSTGIS_USE_TRUE_POSTGIS_TYPES = yes
    SQL_STATEMENT:
      SELECT table_name, column_name, data_type
      FROM information_schema.columns
      where table_schema in ('cb', 'public') and data_type not in ('USER-DEFINED', 'uuid') and column_name not in ('id', 'geom')
      order by table_name, column_name
    RESULT -> StringSearcher_3
StringSearcher_3
    CASE = no
    MATCHED_RESULT_ATTR = _first_match
    REGEXP = (_p$|_l$|_a$)
    STRING_TO_SEARCH = @Value(table_name)
    MATCHED -> AttributeCreator_3
AttributeCreator_3
    ATTR_TABLE = SET_TO classe_original = @Value(table_name)
    -> StringReplacer_2
StringReplacer_2
    CASE = NO
    FIND_TEXT = _p$
    NO_MATCH = _FME_NO_OP_
    REGEXP = YES
    SRC_ATTRS = classe_original
    -> StringReplacer_3
StringReplacer_3
    CASE = NO
    FIND_TEXT = _l$
    NO_MATCH = _FME_NO_OP_
    REGEXP = YES
    SRC_ATTRS = classe_original
    -> StringReplacer_4
StringReplacer_4
    CASE = NO
    FIND_TEXT = _a$
    NO_MATCH = _FME_NO_OP_
    REGEXP = YES
    SRC_ATTRS = classe_original
    -> Sorter
    -> FeatureMerger_2 [REQUESTOR]
Sorter
    SORT_PARM = table_name ALPHA ASCENDING column_name ALPHA ASCENDING
    SORTED -> ListBuilder
ListBuilder
    GROUPS_ORDERED = No
    GROUP_BY = table_name classe_original
    LIST_ATTRS_TO_INCLUDE = column_name
    LIST_NAME = _list
    -> ListConcatenator
ListConcatenator
    DROP_EMPTY_PARTS = No
    LIST_ATTR = _list{}.column_name
    SEP = ,
    VAL_ATTR = _concatenated
    -> DuplicateFilter
    -> DuplicateFilter_2
Note: classes unicas
DuplicateFilter_2
    INPUT_ORDERED_CHOICE = No
    KEYATTR = classe_original
    UNIQUE -> FeatureMerger [REQUESTOR]
Note: conjunto de atributos unicos
DuplicateFilter
    INPUT_ORDERED_CHOICE = No
    KEYATTR = _concatenated classe_original
    UNIQUE -> FeatureMerger [SUPPLIER]
FeatureMerger
    ATTR_ACCUM_MODE = Merge Supplier
    ATTR_CONFLICT_RES = Use Requestor
    IGNORE_NULLS = No
    JOIN_KEYS = @Value(table_name) @Value(table_name) AUTO
    MERGE_TYPE = Attributes Only
    PROCESS_DUPS = NO
    REJECT_NULL_MISSING_KEYS = No
    SUPPLIERS_FIRST = No
    MERGED -> FeatureMerger_2 [SUPPLIER]
    UNMERGED_REQUESTOR -> Terminator
    UNUSED_SUPPLIER -> Terminator
    <REJECTED> -> Terminator
FeatureMerger_2
    ATTR_ACCUM_MODE = Merge Supplier
    ATTR_CONFLICT_RES = Use Requestor
    IGNORE_NULLS = No
    JOIN_KEYS = @Value(table_name) @Value(table_name) AUTO
    MERGE_TYPE = Attributes Only
    PROCESS_DUPS = NO
    REJECT_NULL_MISSING_KEYS = No
    SUPPLIERS_FIRST = No
    MERGED -> AttributeCreator
AttributeCreator
    ATTR_TABLE:
      SET_TO classe = @Value(classe_original)
      SET_TO atributo = @Value(column_name)
      SET_TO tipo = @Value(data_type)
    -> Tester
Tester
    BOOL_OP = AND
    TEST_CLAUSE:
      TEST @Value(classe) != loc_aglomerado_rural
      TEST @Value(classe) != pto_pto_geod_topo_controle
      TEST @Value(classe) != lim_area_politico_adm
      TEST @Value(classe) != lim_area_especial
      TEST @Value(classe) != aux_descontinuidade_geometrica
      TEST @Value(classe) != loc_localidade
      TEST @Value(classe) != veg_vegetacao
      TEST @Value(classe) != aux_area
      TEST @Value(classe) != aux_linha
      TEST @Value(classe) != aux_ponto
    PASSED -> atributos_dsgtools (writer CSV2_1)
atributos_dsgtools (writer CSV2_1)
    attributes: classe string, atributo string, tipo string
Note: diferença entre classes de diferentes geometrias
Terminator
    MESSAGE = Translation Terminated
