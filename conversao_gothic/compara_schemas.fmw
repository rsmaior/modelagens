FME workspace compara_schemas.fmw

Parameters:
- SourceDataset_CSV2 = $(FME_MF_DIR)atributos_gothic.csv   # Source CSV (Comma Separated Value) File(s)
- SourceDataset_CSV2_19 = $(FME_MF_DIR)atributos_dsgtools.csv   # Source CSV (Comma Separated Value) File(s)
- SourceDataset_CSV2_18 = $(FME_MF_DIR)dsgtools\mapeamento_classes.csv   # Source CSV (Comma Separated Value) File(s)
- FEATURE_TYPES_3 =
- SourceDataset_CSV2_15 = $(FME_MF_DIR)dsgtools\mapeamento_atributos.csv   # Source CSV (Comma Separated Value) File(s)
- SourceDataset_CSV2_11 = $(FME_MF_DIR)dsgtools\default_gothic.csv   # Source CSV (Comma Separated Value) File(s)
- SourceDataset_CSV2_10 = $(FME_MF_DIR)dsgtools\default_dsgtools.csv   # Source CSV (Comma Separated Value) File(s)
- SourceDataset_CSV2_12 = $(FME_MF_DIR)browser_gothic.csv   # Source CSV (Comma Separated Value) File(s)
- FEATURE_TYPES =
- SourceDataset_CSV2_14 = $(FME_MF_DIR)modelo_dsgtools.csv   # Source CSV (Comma Separated Value) File(s)
- FEATURE_TYPES_2 =
- SourceDataset_CSV2_13 = $(FME_MF_DIR)dsgtools\mapeamento_dominio.csv   # Source CSV (Comma Separated Value) File(s)

Readers:
- CSV2_1: CSV2 from $(SourceDataset_CSV2)
- CSV2_2: CSV2 from $(SourceDataset_CSV2_19)
- CSV2_3: CSV2 from $(SourceDataset_CSV2_18)
- CSV2_4: CSV2 from $(SourceDataset_CSV2_15)
- CSV2_5: CSV2 from $(SourceDataset_CSV2_11)
- CSV2_6: CSV2 from $(SourceDataset_CSV2_10)
- CSV2_7: CSV2 from $(SourceDataset_CSV2_12)
- CSV2_8: CSV2 from $(SourceDataset_CSV2_14)
- CSV2_9: CSV2 from $(SourceDataset_CSV2_13)

Note: CSV: mapeamento_dominio [CSV2]
CSV (reader CSV2_9)
    attributes: gothic_classe_original string, gothic_atributo string, gothic_code string, gothic_value string, dsgtools_classe_original string, dsgtools_atributo string, dsgtools_code string, dsgtools_value string, direcao string
    -> Tester
Tester
    BOOL_OP = OR
    TEST_CLAUSE = TEST @Value(direcao) = SÓ IDA
    PASSED -> FeatureMerger_13 [SUPPLIER]
    FAILED -> FeatureMerger_14 [SUPPLIER]
Note: dsgtools
CSV (reader CSV2_8)
    attributes: classe string, atributo string, code string, value string, dominio string
    -> AttributeCreator_7
AttributeCreator_7
    ATTR_TABLE = SET_TO classe_original = @Value(classe)
    -> FeatureMerger_14 [REQUESTOR]
FeatureMerger_14
    ATTR_ACCUM_MODE = Merge Supplier
    ATTR_CONFLICT_RES = Use Requestor
    IGNORE_NULLS = No
    JOIN_KEYS = @Value(atributo) @Value(dsgtools_atributo) AUTO @Value(classe) @Value(dsgtools_classe_original) AUTO @Value(code) @Value(dsgtools_code) AUTO
    MERGE_TYPE = Attributes Only
    PROCESS_DUPS = NO
    REJECT_NULL_MISSING_KEYS = No
    SUPPLIERS_FIRST = No
    MERGED -> AttributeCreator_10
    UNMERGED_REQUESTOR -> FeatureMerger_10 [REQUESTOR]
AttributeCreator_10
    ATTR_TABLE:
      SET_TO classe = @Value(gothic_classe_original)
      SET_TO atributo = @Value(gothic_atributo)
      SET_TO code = @Value(gothic_code)
    -> StringCaseChanger_7
StringCaseChanger_7
    ATTRCHOICE = Selected Attributes
    ATTRLIST = atributo classe
    CHANGE_TYPE = lowercase
    -> FeatureMerger_2 [SUPPLIER]
Note: CSV: atributos_gothic [CSV2]
CSV (reader CSV2_1)
    attributes: classe string, atributo string, tipo string
    -> FeatureMerger_7 [REQUESTOR]
Note: CSV: atributos_dsgtools [CSV2]
CSV (reader CSV2_2)
    attributes: classe string, atributo string, tipo string
    -> FeatureMerger_8 [REQUESTOR]
Note: default dsgtools
CSV (reader CSV2_6)
    attributes: dsgtools_classe_original string, dsgtools_atributo string, dsgtools_code string
    -> FeatureMerger_8 [SUPPLIER]
    -> FeatureMerger_10 [SUPPLIER]
FeatureMerger_8
    ATTR_ACCUM_MODE = Merge Supplier
    ATTR_CONFLICT_RES = Use Requestor
    IGNORE_NULLS = No
    JOIN_KEYS = @Value(atributo) @Value(dsgtools_atributo) AUTO @Value(classe) @Value(dsgtools_classe_original) AUTO
    MERGE_TYPE = Attributes Only
    PROCESS_DUPS = NO
    REJECT_NULL_MISSING_KEYS = No
    SUPPLIERS_FIRST = No
    UNMERGED_REQUESTOR -> AttributeCreator_2
AttributeCreator_2
    ATTR_TABLE = SET_TO classe_original = @Value(classe)
    -> FeatureMerger_4 [REQUESTOR]
FeatureMerger_10
    ATTR_ACCUM_MODE = Merge Supplier
    ATTR_CONFLICT_RES = Use Requestor
    IGNORE_NULLS = No
    JOIN_KEYS = @Value(atributo) @Value(dsgtools_atributo) AUTO @Value(classe) @Value(dsgtools_classe_original) AUTO
    MERGE_TYPE = Attributes Only
    PROCESS_DUPS = NO
    REJECT_NULL_MISSING_KEYS = No
    SUPPLIERS_FIRST = No
    UNMERGED_REQUESTOR -> FeatureMerger_6 [REQUESTOR]
Note: mapeamento_atributos
CSV (reader CSV2_4)
    attributes: gothic_classe_original string, gothic_atributo string, dsgtools_classe_original string, dsgtools_atributo string
    -> FeatureMerger_4 [SUPPLIER]
    -> FeatureMerger_6 [SUPPLIER]
FeatureMerger_4
    ATTR_ACCUM_MODE = Merge Supplier
    ATTR_CONFLICT_RES = Use Requestor
    IGNORE_NULLS = No
    JOIN_KEYS = @Value(classe) @Value(dsgtools_classe_original) AUTO @Value(atributo) @Value(dsgtools_atributo) AUTO
    MERGE_TYPE = Attributes Only
    PROCESS_DUPS = NO
    REJECT_NULL_MISSING_KEYS = No
    SUPPLIERS_FIRST = No
    MERGED -> AttributeCreator_4
    UNMERGED_REQUESTOR -> FeatureMerger_3 [REQUESTOR]
AttributeCreator_4
    ATTR_TABLE:
      SET_TO classe = @Value(gothic_classe_original)
      SET_TO atributo = @Value(gothic_atributo)
    -> StringCaseChanger_3
StringCaseChanger_3
    ATTRCHOICE = Selected Attributes
    ATTRLIST = atributo classe
    CHANGE_TYPE = lowercase
    -> Junction
Note: mapeamento_classes
FeatureMerger_6
    ATTR_ACCUM_MODE = Merge Supplier
    ATTR_CONFLICT_RES = Use Requestor
    IGNORE_NULLS = No
    JOIN_KEYS = @Value(classe) @Value(dsgtools_classe_original) AUTO @Value(atributo) @Value(dsgtools_atributo) AUTO
    MERGE_TYPE = Attributes Only
    PROCESS_DUPS = NO
    REJECT_NULL_MISSING_KEYS = No
    SUPPLIERS_FIRST = No
    MERGED -> AttributeCreator_8
    UNMERGED_REQUESTOR -> FeatureMerger_5 [REQUESTOR]
AttributeCreator_8
    ATTR_TABLE:
      SET_TO classe = @Value(gothic_classe_original)
      SET_TO atributo = @Value(gothic_atributo)
    -> StringCaseChanger_6
StringCaseChanger_6
    ATTRCHOICE = Selected Attributes
    ATTRLIST = atributo classe
    CHANGE_TYPE = lowercase
    -> FeatureMerger_2 [SUPPLIER]
Note: default gothic
CSV (reader CSV2_5)
    attributes: gothic_classe_original string, gothic_atributo string, gothic_code string
    -> FeatureMerger_7 [SUPPLIER]
    -> FeatureMerger_9 [SUPPLIER]
FeatureMerger_7
    ATTR_ACCUM_MODE = Merge Supplier
    ATTR_CONFLICT_RES = Use Requestor
    IGNORE_NULLS = No
    JOIN_KEYS = @Value(atributo) @Value(gothic_atributo) AUTO @Value(classe) @Value(gothic_classe_original) AUTO
    MERGE_TYPE = Attributes Only
    PROCESS_DUPS = NO
    REJECT_NULL_MISSING_KEYS = No
    SUPPLIERS_FIRST = No
    UNMERGED_REQUESTOR -> AttributeCreator
AttributeCreator
    ATTR_TABLE:
      SET_TO classe_original = @Value(classe)
      SET_TO atributo_original = @Value(atributo)
    -> StringCaseChanger
StringCaseChanger
    ATTRCHOICE = Selected Attributes
    ATTRLIST = atributo classe
    CHANGE_TYPE = lowercase
    -> DuplicateFilter_2
Note: classe atributo
DuplicateFilter_2
    INPUT_ORDERED_CHOICE = No
    KEYATTR = classe atributo
    UNIQUE -> FeatureMerger [REQUESTOR]
Note: gothic
CSV (reader CSV2_7)
    attributes: classe string, atributo string, code string, value string
    -> AttributeCreator_5
AttributeCreator_5
    ATTR_TABLE:
      SET_TO classe_original = @Value(classe)
      SET_TO atributo_original = @Value(atributo)
    -> FeatureMerger_13 [REQUESTOR]
FeatureMerger_13
    ATTR_ACCUM_MODE = Merge Supplier
    ATTR_CONFLICT_RES = Use Requestor
    IGNORE_NULLS = No
    JOIN_KEYS = @Value(atributo) @Value(gothic_atributo) AUTO @Value(classe) @Value(gothic_classe_original) AUTO @Value(code) @Value(gothic_code) AUTO
    MERGE_TYPE = Attributes Only
    PROCESS_DUPS = NO
    REJECT_NULL_MISSING_KEYS = No
    SUPPLIERS_FIRST = No
    MERGED -> AttributeCreator_9
    UNMERGED_REQUESTOR -> FeatureMerger_9 [REQUESTOR]
AttributeCreator_9
    ATTR_TABLE:
      SET_TO atributo = @Value(dsgtools_atributo)
      SET_TO classe = @Value(dsgtools_classe_original)
      SET_TO code = @Value(dsgtools_code)
    -> StringReplacer_3
StringReplacer_3
    CASE = NO
    FIND_TEXT = (^eco_|^hid_|^enc_|^loc_|^sau_|^edu_|^tra_|^veg_|^lim_|^asb_|^adm_|^pto_|^rel_)
    NO_MATCH = _FME_NO_OP_
    REGEXP = YES
    SRC_ATTRS = classe
    -> FeatureMerger_2 [REQUESTOR]
FeatureMerger_9
    ATTR_ACCUM_MODE = Merge Supplier
    ATTR_CONFLICT_RES = Use Requestor
    IGNORE_NULLS = No
    JOIN_KEYS = @Value(atributo) @Value(gothic_atributo) AUTO @Value(classe) @Value(gothic_classe_original) AUTO
    MERGE_TYPE = Attributes Only
    PROCESS_DUPS = NO
    REJECT_NULL_MISSING_KEYS = No
    SUPPLIERS_FIRST = No
    UNMERGED_REQUESTOR -> StringCaseChanger_4
StringCaseChanger_4
    ATTRCHOICE = Selected Attributes
    ATTRLIST = atributo classe
    CHANGE_TYPE = lowercase
    -> FeatureMerger_2 [REQUESTOR]
Note: mapeamento_classes
CSV (reader CSV2_3)
    attributes: dsgtools_classe_original string, gothic_classe_original string
    -> FeatureMerger_3 [SUPPLIER]
    -> FeatureMerger_5 [SUPPLIER]
FeatureMerger_3
    ATTR_ACCUM_MODE = Merge Supplier
    ATTR_CONFLICT_RES = Use Requestor
    IGNORE_NULLS = No
    JOIN_KEYS = @Value(classe) @Value(dsgtools_classe_original) AUTO
    MERGE_TYPE = Attributes Only
    PROCESS_DUPS = NO
    REJECT_NULL_MISSING_KEYS = No
    SUPPLIERS_FIRST = No
    MERGED -> AttributeCreator_3
    UNMERGED_REQUESTOR -> StringReplacer
AttributeCreator_3
    ATTR_TABLE = SET_TO classe = @Value(gothic_classe_original)
    -> StringCaseChanger_2
StringCaseChanger_2
    ATTRCHOICE = Selected Attributes
    ATTRLIST = classe
    CHANGE_TYPE = lowercase
    -> Junction
StringReplacer
    CASE = NO
    FIND_TEXT = (^eco_|^hid_|^enc_|^loc_|^sau_|^edu_|^tra_|^veg_|^lim_|^asb_|^adm_|^pto_|^rel_)
    NO_MATCH = _FME_NO_OP_
    REGEXP = YES
    SRC_ATTRS = classe
    -> Junction
Junction
    -> DuplicateFilter
Note: classe atributo
DuplicateFilter
    INPUT_ORDERED_CHOICE = No
    KEYATTR = classe atributo
    UNIQUE -> FeatureMerger [SUPPLIER]
FeatureMerger
    ATTR_ACCUM_MODE = Merge Supplier
    ATTR_CONFLICT_RES = Use Requestor
    IGNORE_NULLS = No
    JOIN_KEYS = @Value(classe) @Value(classe) AUTO @Value(atributo) @Value(atributo) AUTO
    MERGE_TYPE = Attributes Only
    PROCESS_DUPS = NO
    REJECT_NULL_MISSING_KEYS = No
    SUPPLIERS_FIRST = No
    UNMERGED_REQUESTOR -> FeatureMerger_UnmergedRequestor
    UNMERGED_REQUESTOR -> FeatureMerger_11 [SUPPLIER]
    UNUSED_SUPPLIER -> FeatureMerger_UnusedSupplier
    UNUSED_SUPPLIER -> FeatureMerger_12 [SUPPLIER]
FeatureMerger_UnmergedRequestor: Inspector [off]
FeatureMerger_UnusedSupplier: Inspector [off]
FeatureMerger_5
    ATTR_ACCUM_MODE = Merge Supplier
    ATTR_CONFLICT_RES = Use Requestor
    IGNORE_NULLS = No
    JOIN_KEYS = @Value(classe) @Value(dsgtools_classe_original) AUTO
    MERGE_TYPE = Attributes Only
    PROCESS_DUPS = NO
    REJECT_NULL_MISSING_KEYS = No
    SUPPLIERS_FIRST = No
    MERGED -> AttributeCreator_6
    UNMERGED_REQUESTOR -> StringReplacer_2
AttributeCreator_6
    ATTR_TABLE = SET_TO classe = @Value(gothic_classe_original)
    -> StringCaseChanger_5
StringCaseChanger_5
    ATTRCHOICE = Selected Attributes
    ATTRLIST = classe
    CHANGE_TYPE = lowercase
    -> FeatureMerger_2 [SUPPLIER]
StringReplacer_2
    CASE = NO
    FIND_TEXT = (^eco_|^hid_|^enc_|^loc_|^sau_|^edu_|^tra_|^veg_|^lim_|^asb_|^adm_|^pto_|^rel_)
    NO_MATCH = _FME_NO_OP_
    REGEXP = YES
    SRC_ATTRS = classe
    -> FeatureMerger_2 [SUPPLIER]
FeatureMerger_2
    ATTR_ACCUM_MODE = Merge Supplier
    ATTR_CONFLICT_RES = Use Requestor
    CLEANING_TOLERANCE = None
    CONNECT_Z_MODE = First Wins
    GEOM_TYPE = Build Polygons
    IGNORE_NULLS = No
    JOIN_KEYS = @Value(classe) @Value(classe) AUTO @Value(atributo) @Value(atributo) AUTO @Value(code) @Value(code) AUTO
    MERGE_TYPE = Attributes Only
    PROCESS_DUPS = YES
    REJECT_NULL_MISSING_KEYS = No
    SUPPLIERS_FIRST = No
    UNMERGED_REQUESTOR -> FeatureMerger_11 [REQUESTOR]
    UNUSED_SUPPLIER -> FeatureMerger_12 [REQUESTOR]
FeatureMerger_11
    ATTR_ACCUM_MODE = Merge Supplier
    ATTR_CONFLICT_RES = Use Requestor
    IGNORE_NULLS = No
    JOIN_KEYS = @Value(atributo) @Value(atributo) AUTO @Value(classe) @Value(classe) AUTO
    MERGE_TYPE = Attributes Only
    PROCESS_DUPS = NO
    REJECT_NULL_MISSING_KEYS = No
    SUPPLIERS_FIRST = No
    UNMERGED_REQUESTOR -> FeatureMerger_2_UnmergedRequestor
FeatureMerger_2_UnmergedRequestor: Inspector
FeatureMerger_12
    ATTR_ACCUM_MODE = Merge Supplier
    ATTR_CONFLICT_RES = Use Requestor
    IGNORE_NULLS = No
    JOIN_KEYS = @Value(atributo) @Value(atributo) AUTO @Value(classe) @Value(classe) AUTO
    MERGE_TYPE = Attributes Only
    PROCESS_DUPS = NO
    REJECT_NULL_MISSING_KEYS = No
    SUPPLIERS_FIRST = No
    UNMERGED_REQUESTOR -> FeatureMerger_2_UnusedSupplier
FeatureMerger_2_UnusedSupplier: Inspector
