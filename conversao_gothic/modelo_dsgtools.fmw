FME workspace modelo_dsgtools.fmw

Parameters:
- SourceDataset_POSTGRES = modelo_dsgtools   # Database
- FEATURE_TYPES = dominios.administracao dominios.antropizada dominios.atividade dominios.bitola dominios.canteirodivisorio dominios.caracteristicafloresta dominios.causa dominios.causaexposicao dominios.chamine dominios.classificacao dominios.classificacaoporte dominios.classificsigiloso dominios.coincidecomdentrode_hid dominios.coincidecomdentrode_lim dominios.coletiva dominios.combrenovavel dominios.compartilhado dominios.construcao dominios.cotacomprovada dominios.cultivopredominante dominios.denominacaoassociada dominios.denso dominios.dentrodepoligono dominios.depressao dominios.destenergelet dominios.destinacaofundeadouro dominios.destinadoa dominios.eixoprincipal dominios.eletrificada dominios.emarruamento dominios.emduto dominios.ensino dominios.especie dominios.especiepredominante dominios.espessalgas dominios.finalidade_asb dominios.finalidade_eco dominios.finalidade_veg dominios.fixa dominios.formaextracao dominios.frigorifico dominios.funcaoedifmetroferrov dominios.geometriaaproximada dominios.geracao dominios.homologacao dominios.indice dominios.instituicao dominios.isolada dominios.jurisdicao dominios.matconstr dominios.materializado dominios.materialpredominante dominios.mattransp dominios.modalidade dominios.modaluso dominios.motivodescontinuidade dominios.multimodal dominios.nascente dominios.navegabilidade dominios.nivelatencao dominios.nrlinhas dominios.ocorrenciaem dominios.operacional dominios.ovgd dominios.poderpublico dominios.posicaopista dominios.posicaorelativa dominios.posicaoreledific dominios.procextracao dominios.proximidade dominios.qualidagua dominios.rede dominios.referencialaltim dominios.referencialgrav dominios.regime dominios.relacionado dominios.relacionado_dut dominios.relacionado_fer dominios.relacionado_hdr dominios.relacionado_hid dominios.relacionado_rod dominios.residuo dominios.revestimento dominios.salinidade dominios.setor dominios.sigla dominios.sistemageodesico dominios.situacaoagua dominios.situacaocosta dominios.situacaoemagua dominios.situacaoespacial dominios.situacaofisica dominios.situacaojuridica dominios.situacaomarco dominios.situamare dominios.terreno dominios.tipoaglomrurisol dominios.tipoalterantrop dominios.tipoareaumida dominios.tipoareausocomun dominios.tipoassociado dominios.tipoatracad dominios.tipobanco dominios.tipobrejopantano dominios.tipocaminhoaereo dominios.tipocampo dominios.tipocampoquadra dominios.tipocapital dominios.tipocemiterio dominios.tipocerr dominios.tipoclassecnae dominios.tipocombustivel dominios.tipocomplexoaero dominios.tipocomplexolazer dominios.tipocomplexoportuario dominios.tipocondutor dominios.tipoconteudo dominios.tipodelimfis dominios.tipodepabast dominios.tipodepgeral dominios.tipodepsaneam dominios.tipodivisaocnae dominios.tipoedifabast dominios.tipoedifaero dominios.tipoedifagropec dominios.tipoedifcivil dominios.tipoedifcomercserv dominios.tipoedifcomunic dominios.tipoedifenergia dominios.tipoediflazer dominios.tipoedifmil dominios.tipoedifport dominios.tipoedifrelig dominios.tipoedifrod dominios.tipoedifsaneam dominios.tipoedifturist dominios.tipoelemnat dominios.tipoentroncamento dominios.tipoequipagropec dominios.tipoestgerad dominios.tipoestmed dominios.tipoestrut dominios.tipoexposicao dominios.tipoextmin dominios.tipofontedagua dominios.tipogrupocnae dominios.tipogrutacaverna dominios.tipoilha dominios.tipolavoura dominios.tipolimareaesp dominios.tipolimintramun dominios.tipolimmassa dominios.tipolimoper dominios.tipolimpol dominios.tipolocalcrit dominios.tipomacchav dominios.tipomaqtermica dominios.tipomarcolim dominios.tipomassadagua dominios.tipoobst dominios.tipooperativo dominios.tipooutlimofic dominios.tipooutunidprot dominios.tipopassagviad dominios.tipopista dominios.tipoplataforma dominios.tipopocomina dominios.tipoponte dominios.tipopostofisc dominios.tipopostopol dominios.tipoprodutoresiduo dominios.tipoptocontrole dominios.tipoptoenergia dominios.tipoptoestmed dominios.tipoptorefgeodtopo dominios.tipoquebramolhe dominios.tipoqueda dominios.tiporecife dominios.tiporef dominios.tiporesiduo dominios.tiporocha dominios.tiposecaocnae dominios.tiposinal dominios.tiposumvert dominios.tipoterrexp dominios.tipotorre dominios.tipotransporte dominios.tipotravessia dominios.tipotravessiaped dominios.tipotrechocomunic dominios.tipotrechoduto dominios.tipotrechoferrov dominios.tipotrechomassa dominios.tipotrechorod dominios.tipotunel dominios.tipounidprotinteg dominios.tipounidusosust dominios.tipousocaminhoaer dominios.tipousoedif dominios.trafego dominios.tratamento dominios.unidadevolume dominios.usopista dominios.usoprincipal
- DestDataset_CSV2 = E:\DINIZ\3_Desenvolvimento\edgv_2.1.3_pro\conversao_gothic   # Destination CSV (Comma Separated Value) Folder

Readers:
- POSTGRES_1: POSTGRES from $(SourceDataset_POSTGRES)

Writers:
- CSV2_1: CSV2 to $(DestDataset_CSV2)

SQLCreator_2
    DATASET = modelo_dsgtools
    EXPOSED_ATTRIBUTE_LIST = table_name,column_name,consrc
    FORMAT = POSTGRES
    POSTGRES_HOST = 10.25.163.12
    POSTGRES_PASSWORD =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
    POSTGRES_PORT = 5432
    POSTGRES_QUERY_FEATURE_TYPES_FOR_MERGE_FILTERS = Yes
    POSTGRES_READ_TIME_WITH_TIMEZONE = Yes
    POSTGRES_SCHEMAS_FOR_TABLE_LISTING = dominios
    POSTGRES_USER_NAME = postgres
    SQL_STATEMENT:
      select distinct tc.table_name, con.consrc, ccu.column_name  from information_schema.table_constraints AS tc
      INNER JOIN pg_catalog.pg_constraint AS con
      ON con.conname = tc.constraint_name
      INNER JOIN information_schema.constraint_column_usage as ccu
      ON ccu.constraint_name = tc.constraint_name
      WHERE tc.constraint_type = 'CHECK' and tc.table_schema in ('cb', 'public')
    RESULT -> StringSearcher_3
StringSearcher_3
    CASE = no
    MATCHED_RESULT_ATTR = _first_match
    REGEXP = (_p$|_l$|_a$)
    STRING_TO_SEARCH = @Value(table_name)
    MATCHED -> ListBuilder_2
    MATCHED -> StringSearcher_2
StringSearcher_2
    CASE = no
    MATCHED_RESULT_ATTR = _first_match
    MATCHES_ATTR = codes
    REGEXP = \d+
    STRING_TO_SEARCH = @Value(consrc)
    MATCHED -> ListExploder
ListExploder
    ATTR_ACCUM_MODE = Merge List Attributes
    ATTR_CONFLICT_RES = Use List Attribute Values
    INDEX_ATTR = _element_index
    LIST_ATTR = codes{}
    ELEMENTS -> Counter
Counter
    CNT_ATTR = _restr_id
    DOMAIN = counter
    SCOPE = Global
    START = 0
    -> ListBuilder_3
ListBuilder_3
    GROUPS_ORDERED = No
    GROUP_BY = table_name column_name match
    LIST_ATTRS_TO_INCLUDE = _restr_id
    LIST_NAME = _list
    -> ListElementCounter_2
ListElementCounter_2
    CNT_ATTR = _presencao_em_restricao
    LIST_NAME = _list{}
    -> FeatureMerger_5 [REQUESTOR]
ListBuilder_2
    GROUPS_ORDERED = No
    GROUP_BY = table_name column_name
    LIST_ATTRS_TO_INCLUDE = consrc
    LIST_NAME = _list
    -> ListElementCounter
ListElementCounter
    CNT_ATTR = _nr_restricao
    LIST_NAME = _list{}
    -> AttributeKeeper_2
AttributeKeeper_2
    KEEP_ATTRS = table_name,column_name,_nr_restricao
    -> FeatureMerger_5 [SUPPLIER]
FeatureMerger_5
    ATTR_ACCUM_MODE = Merge Supplier
    ATTR_CONFLICT_RES = Use Requestor
    IGNORE_NULLS = No
    JOIN_KEYS = @Value(_presencao_em_restricao) @Value(_nr_restricao) AUTO @Value(column_name) @Value(column_name) AUTO @Value(table_name) @Value(table_name) AUTO
    MERGE_TYPE = Attributes Only
    PROCESS_DUPS = NO
    REJECT_NULL_MISSING_KEYS = No
    SUPPLIERS_FIRST = No
    MERGED -> ListExploder_2
ListExploder_2
    ATTR_ACCUM_MODE = Merge List Attributes
    ATTR_CONFLICT_RES = Use List Attribute Values
    INDEX_ATTR = _element_index
    LIST_ATTR = _list{}
    ELEMENTS -> DuplicateFilter_4
DuplicateFilter_4
    INPUT_ORDERED_CHOICE = No
    KEYATTR = table_name column_name match
    UNIQUE -> AttributeKeeper_3
AttributeKeeper_3
    KEEP_ATTRS = table_name,column_name,match
    -> FeatureMerger_3 [SUPPLIER]
    -> AttributeKeeper
AttributeKeeper
    KEEP_ATTRS = table_name,column_name
    -> DuplicateFilter_3
DuplicateFilter_3
    INPUT_ORDERED_CHOICE = No
    KEYATTR = table_name column_name
    UNIQUE -> FeatureMerger_4 [SUPPLIER]
SQLCreator
    DATASET = modelo_dsgtools
    EXPOSED_ATTRIBUTE_LIST = table_name,column_name,dominio
    FORMAT = POSTGRES
    POSTGRES_HOST = 10.25.163.12
    POSTGRES_PASSWORD =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
    POSTGRES_PORT = 5432
    POSTGRES_QUERY_FEATURE_TYPES_FOR_MERGE_FILTERS = Yes
    POSTGRES_READ_TIME_WITH_TIMEZONE = Yes
    POSTGRES_SCHEMAS_FOR_TABLE_LISTING = dominios
    POSTGRES_USER_NAME = postgres
    SQL_STATEMENT:
      select tc.table_name, kcu.column_name, ccu.table_name AS dominio   from information_schema.table_constraints AS tc
      INNER JOIN information_schema.key_column_usage AS kcu
            ON tc.constraint_name = kcu.constraint_name
      INNER JOIN information_schema.constraint_column_usage as ccu
      ON ccu.constraint_name = kcu.constraint_name
      WHERE tc.constraint_type = 'FOREIGN KEY' and tc.table_schema in ('cb', 'public');
    RESULT -> FeatureJoiner [LEFT]
administracao (reader POSTGRES_1)
    attributes: code int2,PrimaryKey, code_name text
    -> AttributeCreator
AttributeCreator
    ATTR_TABLE = SET_TO value = @Value(code_name)
    -> StringReplacer
StringReplacer
    CASE = NO
    FIND_TEXT = dominios.
    NO_MATCH = _FME_NO_OP_
    REGEXP = NO
    SRC_ATTRS = fme_feature_type
    -> FeatureJoiner [RIGHT]
FeatureJoiner
    ATTR_CONFLICT_RES = Use Left
    GEOMETRY_HANDLING = Use Left
    JOIN_KEYS = dominio fme_feature_type AUTO
    JOIN_MODE = Inner
    JOINED -> StringSearcher
StringSearcher
    CASE = no
    MATCHED_RESULT_ATTR = _first_match
    REGEXP = (_p$|_l$|_a$)
    STRING_TO_SEARCH = @Value(table_name)
    MATCHED -> AttributeCreator_3
AttributeCreator_3
    ATTR_TABLE = SET_TO classe_original = @Value(table_name)
    -> FeatureMerger_4 [REQUESTOR]
FeatureMerger_4
    ATTR_ACCUM_MODE = Merge Supplier
    ATTR_CONFLICT_RES = Use Requestor
    IGNORE_NULLS = No
    JOIN_KEYS = @Value(table_name) @Value(table_name) AUTO @Value(column_name) @Value(column_name) AUTO
    MERGE_TYPE = Attributes Only
    PROCESS_DUPS = NO
    REJECT_NULL_MISSING_KEYS = No
    SUPPLIERS_FIRST = No
    MERGED -> FeatureMerger_3 [REQUESTOR]
    UNMERGED_REQUESTOR -> StringReplacer_2
FeatureMerger_3
    ATTR_ACCUM_MODE = Merge Supplier
    ATTR_CONFLICT_RES = Use Requestor
    IGNORE_NULLS = No
    JOIN_KEYS = @Value(table_name) @Value(table_name) AUTO @Value(code) @Value(match) AUTO @Value(column_name) @Value(column_name) AUTO
    MERGE_TYPE = Attributes Only
    PROCESS_DUPS = NO
    REJECT_NULL_MISSING_KEYS = No
    SUPPLIERS_FIRST = No
    MERGED -> StringReplacer_2
StringReplacer_2
    CASE = NO
    FIND_TEXT = _p$
    NO_MATCH = _FME_NO_OP_
    REGEXP = YES
    SRC_ATTRS = classe_original
    -> StringReplacer_3
StringReplacer_3
    CASE = NO
    FIND_TEXT = _l$
    NO_MATCH = _FME_NO_OP_
    REGEXP = YES
    SRC_ATTRS = classe_original
    -> StringReplacer_4
StringReplacer_4
    CASE = NO
    FIND_TEXT = _a$
    NO_MATCH = _FME_NO_OP_
    REGEXP = YES
    SRC_ATTRS = classe_original
    -> Sorter
    -> FeatureMerger_2 [REQUESTOR]
Sorter
    SORT_PARM = table_name ALPHA ASCENDING classe_original ALPHA ASCENDING column_name ALPHA ASCENDING code NUMERIC ASCENDING value ALPHA ASCENDING
    SORTED -> AttributeCreator_4
AttributeCreator_4
    ATTR_TABLE = SET_TO string = @Value(column_name)\@Value(code)\@Value(value)
    -> ListBuilder
ListBuilder
    GROUPS_ORDERED = No
    GROUP_BY = table_name classe_original
    LIST_ATTRS_TO_INCLUDE = string
    LIST_NAME = _list
    -> ListConcatenator
ListConcatenator
    DROP_EMPTY_PARTS = No
    LIST_ATTR = _list{}.string
    SEP = |
    VAL_ATTR = _concatenated
    -> DuplicateFilter
    -> DuplicateFilter_2
DuplicateFilter
    INPUT_ORDERED_CHOICE = No
    KEYATTR = classe_original
    UNIQUE -> FeatureMerger [REQUESTOR]
Note: conjunto de atributos unicos
DuplicateFilter_2
    INPUT_ORDERED_CHOICE = No
    KEYATTR = _concatenated classe_original
    UNIQUE -> FeatureMerger [SUPPLIER]
Note: classes unicas
FeatureMerger
    ATTR_ACCUM_MODE = Merge Supplier
    ATTR_CONFLICT_RES = Use Requestor
    IGNORE_NULLS = No
    JOIN_KEYS = @Value(table_name) @Value(table_name) AUTO
    MERGE_TYPE = Attributes Only
    PROCESS_DUPS = NO
    REJECT_NULL_MISSING_KEYS = No
    SUPPLIERS_FIRST = No
    MERGED -> FeatureMerger_2 [SUPPLIER]
    UNMERGED_REQUESTOR -> Terminator
    UNUSED_SUPPLIER -> Terminator
    <REJECTED> -> Terminator
FeatureMerger_2
    ATTR_ACCUM_MODE = Merge Supplier
    ATTR_CONFLICT_RES = Use Requestor
    IGNORE_NULLS = No
    JOIN_KEYS = @Value(table_name) @Value(table_name) AUTO
    MERGE_TYPE = Attributes Only
    PROCESS_DUPS = NO
    REJECT_NULL_MISSING_KEYS = No
    SUPPLIERS_FIRST = No
    MERGED -> AttributeCreator_2
AttributeCreator_2
    ATTR_TABLE:
      SET_TO classe = @Value(classe_original)
      SET_TO atributo = @Value(column_name)
    -> Tester_2
Tester_2
    BOOL_OP = AND
    TEST_CLAUSE:
      TEST @Value(classe) != loc_aglomerado_rural
      TEST @Value(classe) != pto_pto_geod_topo_controle
      TEST @Value(classe) != lim_area_politico_adm
      TEST @Value(classe) != lim_area_especial
      TEST @Value(classe) != aux_descontinuidade_geometrica
      TEST @Value(classe) != loc_localidade
      TEST @Value(classe) != veg_vegetacao
      TEST @Value(classe) != aux_area
      TEST @Value(classe) != aux_linha
      TEST @Value(classe) != aux_ponto
    PASSED -> modelo_dsgtools (writer CSV2_1)
modelo_dsgtools (writer CSV2_1)
    attributes: classe string, atributo string, code string, value string, dominio string
Note: diferença entre classes de diferentes geometrias
Terminator
    MESSAGE = Translation Terminated
