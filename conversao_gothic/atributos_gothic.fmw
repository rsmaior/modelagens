FME workspace atributos_gothic.fmw

Parameters:
- SourceDataset_TEXTLINE = $(FME_MF_DIR)DSG_EDGV_Modelagem_EDGV.lull   # Source Text File(s)
- DestDataset_CSV2 = E:\DINIZ\3_Desenvolvimento\edgv_2.1.3_pro\conversao_gothic   # Destination CSV (Comma Separated Value) Folder

Readers:
- TEXTLINE_1: TEXTLINE from $(SourceDataset_TEXTLINE)

Writers:
- CSV2_1: CSV2 to $(DestDataset_CSV2)

text_line (reader TEXTLINE_1)
    attributes: text_line_data buffer
    -> StringSearcher_2
StringSearcher_2
    CASE = no
    MATCHED_RESULT_ATTR = _first_match
    REGEXP = definir_atributo_simples
    STRING_TO_SEARCH = @Value(text_line_data)
    MATCHED -> StringSearcher
    NOT_MATCHED -> StringSearcher_3
StringSearcher
    CASE = no
    MATCHED_RESULT_ATTR = _first_match
    MATCHES_ATTR = test
    REGEXP = "\w+"
    STRING_TO_SEARCH = @Value(text_line_data)
    MATCHED -> AttributeCreator
AttributeCreator
    ATTR_TABLE:
      SET_TO classe = @Value(test{0}.match)
      SET_TO atributo = @Value(test{1}.match)
      SET_TO tipo = @Value(test{2}.match)
    -> StringReplacer
StringReplacer
    CASE = NO
    FIND_TEXT = "
    NO_MATCH = _FME_NO_OP_
    REGEXP = NO
    SRC_ATTRS = classe,tipo,atributo
    -> AttributeKeeper_2
AttributeKeeper_2
    KEEP_ATTRS = classe,tipo,atributo
    -> AttributeKeeper
    -> FeatureJoiner [LEFT]
StringSearcher_3
    CASE = no
    MATCHED_RESULT_ATTR = _first_match
    REGEXP = meta_inherit
    STRING_TO_SEARCH = @Value(text_line_data)
    MATCHED -> StringSearcher_4
StringSearcher_4
    CASE = no
    MATCHED_RESULT_ATTR = _first_match
    MATCHES_ATTR = test
    REGEXP = "\w+"
    STRING_TO_SEARCH = @Value(text_line_data)
    MATCHED -> AttributeCreator_2
AttributeCreator_2
    ATTR_TABLE:
      SET_TO filha = @Value(test{0}.match)
      SET_TO pai = @Value(test{1}.match)
    -> StringReplacer_2
StringReplacer_2
    CASE = NO
    FIND_TEXT = "
    NO_MATCH = _FME_NO_OP_
    REGEXP = NO
    SRC_ATTRS = filha,pai
    -> AttributeKeeper_3
AttributeKeeper_3
    KEEP_ATTRS = filha,pai
    -> Tester_5
Tester_5
    BOOL_OP = OR
    TEST_CLAUSE = TEST @Value(pai) != ""
    PASSED -> PythonCaller
PythonCaller
    NEW_ATTRIBUTES = filha pai
    PYTHONSOURCE:
      import fme
      import fmeobjects

      # Template Class Interface:
      # When using this class, make sure its name is set as the value of
      # the 'Class or Function to Process Features' transformer parameter
      class FeatureProcessor(object):
          def __init__(self):
              self.featureList = []
          def input(self,feature):
              self.featureList.append(feature)
          def getParent(self, pai):
              parents = [pai]
              for feature in self.featureList:
                  if feature.getAttribute('filha') == pai:
                      parents = parents + self.getParent(feature.getAttribute('pai'))
              return parents
          def close(self):
              for feature in self.featureList:
                  parents = self.getParent(feature.getAttribute('pai'))
                  for parent in parents:
                      newFeature = fmeobjects.FMEFeature()
                      newFeature.setAttribute('filha', feature.getAttribute('filha'))
                      newFeature.setAttribute('pai', parent)
                      self.pyoutput(newFeature)
    PYTHONSYMBOL = FeatureProcessor
    -> FeatureJoiner [RIGHT]
FeatureJoiner
    ATTR_CONFLICT_RES = Use Left
    GEOMETRY_HANDLING = Use Left
    JOIN_KEYS = classe pai AUTO
    JOIN_MODE = Inner
    JOINED -> AttributeCreator_3
AttributeCreator_3
    ATTR_TABLE = SET_TO classe = @Value(filha)
    -> AttributeKeeper
AttributeKeeper
    KEEP_ATTRS = classe,tipo,atributo
    -> Tester_7
Tester_7
    BOOL_OP = AND
    TEST_CLAUSE:
      CASE_SENSITIVE_TEST @Value(atributo) NOT_IN     ordemTickDepressao,justTxt,visivel,repTipoTxt,necessidadeManutencao,tipoRepresentacao
      CASE_SENSITIVE_TEST @Value(atributo) NOT_= escalaMaxSimbolizar
      CASE_SENSITIVE_TEST @Value(atributo) NOT_= escalaDosDadosEDGV
      CASE_SENSITIVE_TEST @Value(atributo) NOT_BEGINS_WITH fk
      CASE_SENSITIVE_TEST @Value(atributo) NOT_= justTxtAltitude
      CASE_SENSITIVE_TEST @Value(atributo) NOT_= justTxtTipo
      CASE_SENSITIVE_TEST @Value(atributo) NOT_= latitude_txt
      CASE_SENSITIVE_TEST @Value(atributo) NOT_= longitude_txt
      CASE_SENSITIVE_TEST @Value(atributo) NOT_BEGINS_WITH offSet
      CASE_SENSITIVE_TEST @Value(atributo) NOT_= ordemTickDepressao
      CASE_SENSITIVE_TEST @Value(atributo) NOT_= orientacao
      CASE_SENSITIVE_TEST @Value(atributo) NOT_= simbolizar
      CASE_SENSITIVE_TEST @Value(atributo) NOT_= tamanhoTxt
    PASSED -> Tester_6
Tester_6
    BOOL_OP = OR
    TEST_CLAUSE = CASE_SENSITIVE_TEST @Value(classe) NOT_IN Classificador_Orig_Prec_Acur,Linha_Generica_Edicao,Area_Generica_Edicao,Simb_Hidrografia,Texto_Generico_Edicao_Mini,Texto_Generico_Edicao,Simb_Ext_Mineral,Simb_Limite_Area_Especial,Simb_Limite_Politico_Adm,Simb_Trecho_Duto,Simb_Trecho_Hidroviario,Simb_Trecho_Rodoviario,Simb_Trecho_Ferroviario,Simb_Curva_Mestra,Area_Nao_Mapeada,Ponto_Turistico,Complexo_Abast_Agua,Complexo_Aeroportuario,Complexo_Comunicacao,Complexo_Gerad_Energ_Eletr,Complexo_Lazer,Complexo_Portuario,Complexo_Saneamento,Estrut_Apoio,Frigorifico_Matadouro,Instituicao_Publica,Madeireira,Org_Agrop_Ext_Veg_Pesca,Org_Comerc_Serv,Org_Ensino,Org_Ext_Mineral,Org_Industrial,Org_Militar_Ensino,Org_Militar_Saude,Org_Pub_Civil,Org_Pub_Ensino,Org_Pub_Militar,Org_Pub_Saude,Org_Pub_Servico_Social,Org_Religiosa,Org_Religiosa_Ensino,Org_Saude,Org_Servico_Social,Subest_Transm_Energ_Eletr,Est_Med_Fenomenos,Hidrovia
    PASSED -> Tester_4
Tester_4
    BOOL_OP = AND
    TEST_CLAUSE:
      CASE_SENSITIVE_TEST @Value(classe) NOT_= Classificador_Orig_Prec_Acur
      CASE_SENSITIVE_TEST @Value(classe) NOT_= EDGV_MODELO
      CASE_SENSITIVE_TEST @Value(classe) NOT_= Area_Nao_Mapeada
      CASE_SENSITIVE_TEST @Value(classe) NOT_= _Padrao_DGN
      CASE_SENSITIVE_TEST @Value(classe) NOT_= _Simb_Texto
      CASE_SENSITIVE_TEST @Value(classe) NOT_= _txt_cota
      CASE_SENSITIVE_TEST @Value(classe) NOT_= _txt_simb_curva
      CASE_SENSITIVE_TEST @Value(classe) NOT_= AREA_DELIMITADORA
      CASE_SENSITIVE_TEST @Value(classe) NOT_= area_relatorio_ligacao
      CASE_SENSITIVE_TEST @Value(classe) NOT_= areas_genericas
      CASE_SENSITIVE_TEST @Value(classe) NOT_= Bandeira_Edif
      CASE_SENSITIVE_TEST @Value(classe) NOT_= centroides
      CASE_SENSITIVE_TEST @Value(classe) NOT_= Complexo_Habitacional
      CASE_SENSITIVE_TEST @Value(classe) NOT_= contornos
      CASE_SENSITIVE_TEST @Value(classe) NOT_= Curso_Dagua
      CASE_SENSITIVE_TEST @Value(classe) NOT_= Curva_Forma
      CASE_SENSITIVE_TEST @Value(classe) NOT_= fkClassificador
      CASE_SENSITIVE_TEST @Value(classe) NOT_= Isolinha_Hipsografica
      CASE_SENSITIVE_TEST @Value(classe) NOT_= Sentido_Corrente
      CASE_SENSITIVE_TEST @Value(classe) NOT_= Simb_Elemento_Fisiog_Nat
      CASE_SENSITIVE_TEST @Value(classe) NOT_= Simb_Trecho_Comunic
      CASE_SENSITIVE_TEST @Value(classe) NOT_= Simb_Trecho_Energia
      CASE_SENSITIVE_TEST @Value(classe) NOT_= Via_Rodoviaria
      CASE_SENSITIVE_TEST @Value(classe) NOT_BEGINS_WITH centroide_de_
      CASE_SENSITIVE_TEST @Value(classe) NOT_BEGINS_WITH Via_Transporte_
      CASE_SENSITIVE_TEST @Value(classe) NOT_= Trecho_Curso_Dagua
      CASE_SENSITIVE_TEST @Value(classe) NOT_= Estrut_Transporte
      CASE_SENSITIVE_TEST @Value(classe) NOT_= _Geometria_Aproximada
      CASE_SENSITIVE_TEST @Value(classe) NOT_= _Nome_NomeAbrev
      CASE_SENSITIVE_TEST @Value(classe) NOT_= DESCONTINUIDADE_GEOMETRIA
      CASE_SENSITIVE_TEST @Value(classe) NOT_= EDIFICACAO
      CASE_SENSITIVE_TEST @Value(classe) NOT_= LIMITES
      CASE_SENSITIVE_TEST @Value(classe) NOT_= LOCALIDADE
      CASE_SENSITIVE_TEST @Value(classe) NOT_= Torre
      CASE_SENSITIVE_TEST @Value(classe) NOT_= Trecho_Comunic_Energia
      CASE_SENSITIVE_TEST @Value(classe) NOT_= Unidade_Conservacao_SNUC
      CASE_SENSITIVE_TEST @Value(classe) NOT_= Unidade_Conservacao
      CASE_SENSITIVE_TEST @Value(classe) NOT_= Veg_Natural
      CASE_SENSITIVE_TEST @Value(classe) NOT_= VEGETACAO
      CASE_SENSITIVE_TEST @Value(classe) NOT_= Vegetacao
      CASE_SENSITIVE_TEST @Value(classe) NOT_= Via_Ferrea
      CASE_SENSITIVE_TEST @Value(classe) NOT_= _coringa_TBCD_aquisicao
      CASE_SENSITIVE_TEST @Value(classe) NOT_= area_criada_inner_ring
      CASE_SENSITIVE_TEST @Value(classe) NOT_= _coringa_TBCD_validacao
      CASE_SENSITIVE_TEST @Value(classe) NOT_= Pto_Geod_Topo_Controle
      CASE_SENSITIVE_TEST @Value(classe) NOT_= Obra_Transporte
      CASE_SENSITIVE_TEST @Value(classe) NOT_BEGINS_WITH contorno_de_
      CASE_SENSITIVE_TEST @Value(classe) NOT_BEGINS_WITH area_de_
      CASE_SENSITIVE_TEST @Value(classe) NOT_= area_criada_outer_ring
      CASE_SENSITIVE_TEST @Value(classe) NOT_= Ponte_Pass_Elevada_Viaduto
      CASE_SENSITIVE_TEST @Value(classe) NOT_= Aldeia_Indigena
      CASE_SENSITIVE_TEST @Value(classe) NOT_= Unidades_Protegidas
      CASE_SENSITIVE_TEST @Value(classe) NOT_= Duto
      CASE_SENSITIVE_TEST @Value(classe) NOT_= Elemento_Fisiografico
      CASE_SENSITIVE_TEST @Value(classe) NOT_= Localidade
      CASE_SENSITIVE_TEST @Value(classe) NOT_= Veg_Desconhecida
    PASSED -> atributos_gothic (writer CSV2_1)
atributos_gothic (writer CSV2_1)
    attributes: classe string, atributo string, tipo string
